[DOCUMENT]
TITLE: L1 — System Goals
UID: QMGMT-L1
VERSION: 0.1
OPTIONS:
  MARKUP: RST
  AUTO_LEVELS: On

[GRAMMAR]
IMPORT_FROM_FILE: requirements.sgra

[SYSTEM_GOAL]
UID: L1-STATE
TITLE: Enforce State
STATEMENT: >>>
An administrator shall be able to declare the intended state of qubes and system resources and
have the system brought to it.
<<<
PRODUCT: Ansible, Salt, QubesadminTools, Terraform

[SYSTEM_GOAL]
UID: L1-OPERATE
TITLE: Transient Action
STATEMENT: >>>
An administrator shall be able to act on qubes on demand: start, stop, pause, attach devices,
run commands.
<<<
PRODUCT: Ansible, Salt, QubesadminTools

[SYSTEM_GOAL]
UID: L1-RECONCILE
TITLE: Reconcile State
STATEMENT: >>>
The system shall remain in its declared state over time: divergence introduced outside management
shall be detected and brought back to the declared state.
<<<
PRODUCT: Terraform

[SYSTEM_GOAL]
UID: L1-ISOLATION
TITLE: Management qube security
STATEMENT: >>>
Administering a qube shall never cause data originating from that qube to be
interpreted by a management qube, unless it is trivial to parse.
<<<
PRODUCT: Ansible, Salt, QubesadminTools, Terraform
RATIONALE: >>>
A management qube has control of the qubes it manages, so vulnerabilities in the parsing of managed-qube-supplied data may lead to total compromise of all qubes under its management. `QSB #45 <https://www.qubes-os.org/news/2018/12/03/qsb-45/>`__ established the
countermeasure now common to the tooling: configuration work runs inside a per-target management disposable qube rather than in dom0 / management qubes.

Trivial-to-parse data such as progress information can be used directly without an intermediate disposable, so long as the parsing is hardened.
<<<

[SYSTEM_GOAL]
UID: L1-ADMINAPI
TITLE: Admin API through policy system in management qube
STATEMENT: >>>
Every administrative action shall be performed through a qrexec-mediated interface from a management qube with the necessary `Qubes Admin API <https://doc.qubes-os.org/en/latest/developer/services/admin-api.html>`__ calls and `policies <https://www.qubes-os.org/news/2020/06/22/new-qrexec-policy-system/>`__.
<<<
PRODUCT: Ansible, Salt, QubesadminTools, Terraform
RATIONALE: >>>
Qrexec policy is the authoritative access control over administration in Qubes OS.
<<<

[SYSTEM_GOAL]
UID: L1-OBSERVABILITY
TITLE: Inspectable state and reviewable changes
STATEMENT: >>>
An administrator shall be able to inspect current state, preview a change before
applying it, and obtain an unambiguous account of what changed and what failed.
<<<
PRODUCT: Ansible, Salt, QubesadminTools, Terraform
RATIONALE: >>>
Administrative errors in dom0 are expensive and hard to reverse. Previewing a
change is the primary defence, so a dry run that silently mutates state is worse
than none.
<<<
