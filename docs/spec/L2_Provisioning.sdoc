[DOCUMENT]
TITLE: L2 — Provisioning
UID: QMGMT-L2P
VERSION: 0.1
OPTIONS:
  MARKUP: RST
  AUTO_LEVELS: On

[GRAMMAR]
IMPORT_FROM_FILE: requirements.sgra

[[SECTION]]
TITLE: Qube lifecycle

[PRODUCT_REQUIREMENT]
UID: L2P-LIFECYCLE-010
TITLE: Qube creation
STATEMENT: >>>
The management tool shall create a qube of a caller-specified class from a
caller-specified template.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_create

[PRODUCT_REQUIREMENT]
UID: L2P-LIFECYCLE-020
TITLE: Qube cloning
STATEMENT: >>>
The management tool shall create a new qube as a copy of an existing qube,
including that qube's configuration.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_create
- TYPE: File
  ROLE: Authority
  PATH: qubes-core-admin/qubes/api/admin.py
  ELEMENT: function
  ID: QubesAdminAPI.vm_volume_clone_to

[PRODUCT_REQUIREMENT]
UID: L2P-LIFECYCLE-021
TITLE: Qube renaming
STATEMENT: >>>
The management tool shall rename an existing qube, preserving its storage and the
settings of qubes that refer to it.
<<<
EARS_PATTERN: Ubiquitous
PRODUCT: Ansible, Salt, QubesTools, Terraform
RATIONALE: >>>
qubesd treats a qube's name as write-once, so a rename is a clone under the new
name, repointing of the qubes that use it, and removal of the original.
<<<
RELATIONS:
- TYPE: Parent
  VALUE: L1-STATE
  ROLE: Refines
- TYPE: File
  ROLE: Authority
  PATH: qubes-core-admin/qubes/api/admin.py
  ELEMENT: function
  ID: QubesAdminAPI.vm_create
- TYPE: File
  ROLE: Authority
  PATH: qubes-core-admin/qubes/api/admin.py
  ELEMENT: function
  ID: QubesAdminAPI.vm_volume_clone_to
- TYPE: File
  ROLE: Authority
  PATH: qubes-core-admin/qubes/api/admin.py
  ELEMENT: function
  ID: QubesAdminAPI.vm_remove

[PRODUCT_REQUIREMENT]
UID: L2P-LIFECYCLE-030
TITLE: Qube removal
STATEMENT: >>>
The management tool shall remove a qube together with its storage volumes.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_remove

[PRODUCT_REQUIREMENT]
UID: L2P-LIFECYCLE-040
TITLE: Qube start
STATEMENT: >>>
The management tool shall start a halted qube and report completion only once
that qube is running.
<<<
EARS_PATTERN: Ubiquitous
PRODUCT: Ansible, Salt, QubesTools
RELATIONS:
- TYPE: Parent
  VALUE: L1-OPERATE
  ROLE: Refines
- TYPE: File
  ROLE: Authority
  PATH: qubes-core-admin/qubes/api/admin.py
  ELEMENT: function
  ID: QubesAdminAPI.vm_start

[PRODUCT_REQUIREMENT]
UID: L2P-LIFECYCLE-050
TITLE: Qube shutdown and kill
STATEMENT: >>>
The management tool shall bring a running qube to the halted state by a
caller-selected graceful shutdown or forced kill.
<<<
EARS_PATTERN: Ubiquitous
PRODUCT: Ansible, Salt, QubesTools
RELATIONS:
- TYPE: Parent
  VALUE: L1-OPERATE
  ROLE: Refines
- TYPE: File
  ROLE: Authority
  PATH: qubes-core-admin/qubes/api/admin.py
  ELEMENT: function
  ID: QubesAdminAPI.vm_shutdown
- TYPE: File
  ROLE: Authority
  PATH: qubes-core-admin/qubes/api/admin.py
  ELEMENT: function
  ID: QubesAdminAPI.vm_kill

[PRODUCT_REQUIREMENT]
UID: L2P-LIFECYCLE-060
TITLE: Qube pause and resume
STATEMENT: >>>
The management tool shall transition a qube between the running and paused
execution states on request.
<<<
EARS_PATTERN: Ubiquitous
PRODUCT: Ansible, Salt, QubesTools
RELATIONS:
- TYPE: Parent
  VALUE: L1-OPERATE
  ROLE: Refines
- TYPE: File
  ROLE: Authority
  PATH: qubes-core-admin/qubes/api/admin.py
  ELEMENT: function
  ID: QubesAdminAPI.vm_pause
- TYPE: File
  ROLE: Authority
  PATH: qubes-core-admin/qubes/api/admin.py
  ELEMENT: function
  ID: QubesAdminAPI.vm_unpause

[PRODUCT_REQUIREMENT]
UID: L2P-LIFECYCLE-070
TITLE: Existing qube adoption
STATEMENT: >>>
The management tool shall bring an existing qube under management without recreating or modifying
it.
<<<
EARS_PATTERN: Ubiquitous
PRODUCT: Terraform
RELATIONS:
- TYPE: Parent
  VALUE: L1-RECONCILE
  ROLE: Refines

[[/SECTION]]

[[SECTION]]
TITLE: Qube attributes

[PRODUCT_REQUIREMENT]
UID: L2P-CONFIG-010
TITLE: Qube property configuration
STATEMENT: >>>
The management tool shall set each qube property named in the desired state to
the value given there.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_property_set

[PRODUCT_REQUIREMENT]
UID: L2P-CONFIG-020
TITLE: Property reset to default
STATEMENT: >>>
The management tool shall restore a qube property to its default value on
request.
<<<
EARS_PATTERN: Ubiquitous
PRODUCT: Ansible, Salt, QubesTools, Terraform
RATIONALE: >>>
A property holding its default is not the same state as a property explicitly
set to the same value, because the default tracks later system changes.
<<<
RELATIONS:
- TYPE: Parent
  VALUE: L1-STATE
  ROLE: Refines
- TYPE: File
  ROLE: Authority
  PATH: qubes-core-admin/qubes/api/admin.py
  ELEMENT: function
  ID: QubesAdminAPI.vm_property_reset

[PRODUCT_REQUIREMENT]
UID: L2P-CONFIG-030
TITLE: Qube feature configuration
STATEMENT: >>>
The management tool shall bring a qube's features to the set of values given in
the desired state.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_feature_set

[PRODUCT_REQUIREMENT]
UID: L2P-CONFIG-040
TITLE: Qube service configuration
STATEMENT: >>>
The management tool shall set a named qube service to enabled or disabled
through its corresponding service feature.
<<<
EARS_PATTERN: Ubiquitous
PRODUCT: Ansible, Salt, QubesTools, Terraform
RATIONALE: >>>
Services have no storage of their own; a service is the feature named
``service.<name>``, so the two views must not diverge.
<<<
RELATIONS:
- TYPE: Parent
  VALUE: L1-STATE
  ROLE: Refines
- TYPE: File
  ROLE: Authority
  PATH: qubes-core-admin/qubes/api/admin.py
  ELEMENT: function
  ID: QubesAdminAPI.vm_feature_set

[PRODUCT_REQUIREMENT]
UID: L2P-CONFIG-050
TITLE: Qube tag configuration
STATEMENT: >>>
The management tool shall bring a qube's tag set to the tags given in the
desired state.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_tag_set
- TYPE: File
  ROLE: Authority
  PATH: qubes-core-admin/qubes/api/admin.py
  ELEMENT: function
  ID: QubesAdminAPI.vm_tag_remove

[PRODUCT_REQUIREMENT]
UID: L2P-CONFIG-060
TITLE: Qube notes
STATEMENT: >>>
The management tool shall set the free-form notes attached to a qube.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_notes_set

[PRODUCT_REQUIREMENT]
UID: L2P-CONFIG-070
TITLE: Notes size limit
STATEMENT: >>>
If notes exceed 256 000 bytes, then the management tool shall reject the
change and leave the stored notes untouched.
<<<
EARS_PATTERN: Unwanted-behaviour
PRODUCT: Ansible, QubesTools, Terraform
RATIONALE: >>>
Notes are qube-visible text held in dom0, so the Admin API caps them at 256 000 bytes.
Scoped to the components that expose notes; the wider gap is carried by
L2P-CONFIG-060.
<<<
RELATIONS:
- TYPE: Parent
  VALUE: L1-STATE
  ROLE: Refines
- TYPE: Parent
  VALUE: L1-ISOLATION
  ROLE: Refines
- TYPE: File
  ROLE: Authority
  PATH: qubes-core-admin/qubes/api/admin.py
  ELEMENT: function
  ID: QubesAdminAPI.vm_notes_set

[PRODUCT_REQUIREMENT]
UID: L2P-CONFIG-080
TITLE: Qube class immutability
STATEMENT: >>>
The management tool shall reject a request to change the class of an existing
qube.
<<<
EARS_PATTERN: Ubiquitous
PRODUCT: Ansible, Salt, QubesTools, Terraform
RATIONALE: >>>
Class fixes a qube's storage layout and startup semantics at creation, so a
declared class change is a request to recreate, never to mutate.
<<<
RELATIONS:
- TYPE: Parent
  VALUE: L1-STATE
  ROLE: Refines
- TYPE: File
  ROLE: Authority
  PATH: qubes-core-admin/qubes/api/admin.py
  ELEMENT: function
  ID: QubesAdminAPI.vm_create

[[/SECTION]]

[[SECTION]]
TITLE: Storage and volumes

[PRODUCT_REQUIREMENT]
UID: L2P-STORAGE-010
TITLE: Volume resize
STATEMENT: >>>
The management tool shall resize a qube volume to a caller-specified size.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_volume_resize

[PRODUCT_REQUIREMENT]
UID: L2P-STORAGE-020
TITLE: Volume revision retention
STATEMENT: >>>
The management tool shall set the number of snapshot revisions retained for a
qube volume.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_volume_set_revisions_to_keep

[PRODUCT_REQUIREMENT]
UID: L2P-STORAGE-030
TITLE: Storage pool selection
STATEMENT: >>>
The management tool shall place a qube's volumes in a caller-specified storage
pool.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_create_in_pool

[[/SECTION]]

[[SECTION]]
TITLE: Device assignment

[PRODUCT_REQUIREMENT]
UID: L2P-DEVICE-010
TITLE: Transient device attachment
STATEMENT: >>>
The management tool shall attach a device to a qube for the lifetime of that
qube's current run.
<<<
EARS_PATTERN: Ubiquitous
PRODUCT: Salt, QubesTools
RATIONALE: >>>
An attachment does not survive a restart, so it is an operation rather than
declarable state; the Ansible collection deliberately manages assignments only.
<<<
RELATIONS:
- TYPE: Parent
  VALUE: L1-OPERATE
  ROLE: Refines
- TYPE: Parent
  VALUE: L1-ADMINAPI
  ROLE: Refines
- TYPE: File
  ROLE: Authority
  PATH: qubes-core-admin/qubes/api/admin.py
  ELEMENT: function
  ID: QubesAdminAPI.vm_device_attach

[PRODUCT_REQUIREMENT]
UID: L2P-DEVICE-020
TITLE: Persistent device assignment
STATEMENT: >>>
The management tool shall assign a device to a qube so that the assignment
survives a restart of that qube.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_device_assign

[PRODUCT_REQUIREMENT]
UID: L2P-DEVICE-030
TITLE: Device assignment modes
STATEMENT: >>>
The management tool shall set a device assignment's mode to ask-to-attach,
auto-attach or required.
<<<
EARS_PATTERN: Ubiquitous
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_device_set_required

[PRODUCT_REQUIREMENT]
UID: L2P-DEVICE-040
TITLE: PCI assignment constraint
STATEMENT: >>>
If a PCI device is bound to a qube, then the management tool shall record it as
a required assignment rather than an attachment.
<<<
EARS_PATTERN: Unwanted-behaviour
PRODUCT: Ansible, Salt, QubesTools, Terraform
RATIONALE: >>>
PCI passthrough is fixed at qube start, so any weaker binding leaves the qube
running without the device it was configured to have.
<<<
RELATIONS:
- TYPE: Parent
  VALUE: L1-STATE
  ROLE: Refines
- TYPE: File
  ROLE: Authority
  PATH: qubes-core-admin/qubes/api/admin.py
  ELEMENT: function
  ID: QubesAdminAPI.vm_device_assign

[[/SECTION]]

[[SECTION]]
TITLE: Network and firewall

[PRODUCT_REQUIREMENT]
UID: L2P-NET-010
TITLE: Netvm validation
STATEMENT: >>>
If the qube named as netvm does not provide network, then the management tool
shall reject the change.
<<<
EARS_PATTERN: Unwanted-behaviour
PRODUCT: Ansible, Salt, QubesTools, Terraform
RELATIONS:
- TYPE: Parent
  VALUE: L1-STATE
  ROLE: Refines
- TYPE: File
  ROLE: Authority
  PATH: qubes-core-admin/qubes/api/admin.py
  ELEMENT: function
  ID: QubesAdminAPI.vm_property_set

[PRODUCT_REQUIREMENT]
UID: L2P-NET-020
TITLE: Firewall rule set
STATEMENT: >>>
The management tool shall apply an ordered set of firewall rules to a qube,
replacing the rules previously in force.
<<<
EARS_PATTERN: Ubiquitous
PRODUCT: Ansible, Salt, QubesTools, Terraform
RATIONALE: >>>
Rules are evaluated in order and the first match wins, so a rule set is only
meaningful as a whole sequence.
<<<
RELATIONS:
- TYPE: Parent
  VALUE: L1-STATE
  ROLE: Refines
- TYPE: File
  ROLE: Authority
  PATH: qubes-core-admin/qubes/api/admin.py
  ELEMENT: function
  ID: QubesAdminAPI.vm_firewall_set

[[/SECTION]]

[[SECTION]]
TITLE: Software and templates

[PRODUCT_REQUIREMENT]
UID: L2P-SW-020
TITLE: Template installation
STATEMENT: >>>
The management tool shall install a template from a configured template
repository.
<<<
EARS_PATTERN: Ubiquitous
PRODUCT: Ansible, Salt, QubesTools, Terraform
RELATIONS:
- TYPE: Parent
  VALUE: L1-STATE
  ROLE: Refines

[PRODUCT_REQUIREMENT]
UID: L2P-SW-030
TITLE: Template signature verification
STATEMENT: >>>
The management tool shall verify the cryptographic signature of a downloaded
template before installing it.
<<<
EARS_PATTERN: Ubiquitous
PRODUCT: Ansible, Salt, QubesTools, Terraform
RATIONALE: >>>
Template packages are unpacked in a management qube, so an unverified download
is a direct management qube code-execution path.
<<<
RELATIONS:
- TYPE: Parent
  VALUE: L1-STATE
  ROLE: Refines
- TYPE: Parent
  VALUE: L1-ISOLATION
  ROLE: Refines

[[/SECTION]]

[[SECTION]]
TITLE: Qubes system

[PRODUCT_REQUIREMENT]
UID: L2P-SYSTEM-010
TITLE: Global property configuration
STATEMENT: >>>
The management tool shall set each global Qubes property named in the desired state to the value
given there.
<<<
EARS_PATTERN: Ubiquitous
PRODUCT: Terraform
RELATIONS:
- TYPE: Parent
  VALUE: L1-STATE
  ROLE: Refines
- TYPE: File
  ROLE: Authority
  PATH: qubes-core-admin/qubes/api/admin.py
  ELEMENT: function
  ID: QubesAdminAPI.property_set

[PRODUCT_REQUIREMENT]
UID: L2P-SYSTEM-050
TITLE: qrexec policy management
STATEMENT: >>>
The management tool shall bring a named qrexec policy file to the rules given in the desired state.
<<<
EARS_PATTERN: Ubiquitous
PRODUCT: Terraform
RELATIONS:
- TYPE: Parent
  VALUE: L1-STATE
  ROLE: Refines
- TYPE: Parent
  VALUE: L1-ADMINAPI
  ROLE: Refines

[[/SECTION]]

[[SECTION]]
TITLE: Inspection

[PRODUCT_REQUIREMENT]
UID: L2P-INSPECT-020
TITLE: Power state reporting
STATEMENT: >>>
The management tool shall report the current power state of a qube.
<<<
EARS_PATTERN: Ubiquitous
PRODUCT: Ansible, Salt, QubesTools
RELATIONS:
- TYPE: Parent
  VALUE: L1-OPERATE
  ROLE: Refines
- TYPE: Parent
  VALUE: L1-OBSERVABILITY
  ROLE: Refines
- TYPE: File
  ROLE: Authority
  PATH: qubes-core-admin/qubes/api/admin.py
  ELEMENT: function
  ID: QubesAdminAPI.vm_current_state

[[/SECTION]]

[[SECTION]]
TITLE: Drift and recovery

[PRODUCT_REQUIREMENT]
UID: L2P-CONV-060
TITLE: Drift detection
STATEMENT: >>>
When a managed object's live configuration differs from the recorded state, the management tool
shall report that difference in the change preview.
<<<
EARS_PATTERN: Event-driven
PRODUCT: Terraform
RELATIONS:
- TYPE: Parent
  VALUE: L1-RECONCILE
  ROLE: Refines
- TYPE: Parent
  VALUE: L1-OBSERVABILITY
  ROLE: Refines

[PRODUCT_REQUIREMENT]
UID: L2P-CONV-070
TITLE: Drift correction
STATEMENT: >>>
When a managed qube was changed or removed outside the tool, the management tool shall restore its
declared state on the next run.
<<<
EARS_PATTERN: Event-driven
PRODUCT: Terraform
RELATIONS:
- TYPE: Parent
  VALUE: L1-RECONCILE
  ROLE: Refines

[PRODUCT_REQUIREMENT]
UID: L2P-CONV-080
TITLE: Failed-creation rollback
STATEMENT: >>>
If creating a qube fails, then the management tool shall remove only objects that the failed run
itself created.
<<<
EARS_PATTERN: Unwanted-behaviour
PRODUCT: Terraform
RATIONALE: >>>
A rollback that deletes a pre-existing qube destroys data the run never owned.
<<<
RELATIONS:
- TYPE: Parent
  VALUE: L1-RECONCILE
  ROLE: Refines

[[/SECTION]]
